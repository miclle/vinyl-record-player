"""Generate and reopen the independent D port without saving other documents."""
from pathlib import Path
import sys

import FreeCAD as App
import FreeCADGui as Gui

tools = Path(__file__).resolve().parent
if str(tools) not in sys.path:
    sys.path.insert(0, str(tools))
source = tools / 'build_bass_port_print.py'
namespace = {'__name__': 'bass_port_print_macro', '__file__': str(source)}
exec(compile(source.read_bytes(), str(source), 'exec'), namespace)
namespace['export']()
doc = App.openDocument(str(namespace['OUTPUT'] / (namespace['STEMS']['BassPort'] + '.FCStd')))
if not all(obj.ViewObject.Visibility for obj in doc.Objects):
    raise RuntimeError('Saved port reopened hidden')
Gui.getDocument(doc.Name).activeView().fitAll()
