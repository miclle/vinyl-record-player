# Run from FreeCAD: Macro > Macros > Execute. The file location determines repo root.
import json
import sys
import importlib.util
from pathlib import Path
import FreeCAD as App
import FreeCADGui as Gui

macro_path = Path(__file__).resolve()
if str(macro_path.parent) not in sys.path:
    sys.path.insert(0, str(macro_path.parent))

def load_local_module(name):
    # Read source directly: repeated macros must not reuse modules or stale pyc.
    path = macro_path.parent / (name + '.py')
    spec = importlib.util.spec_from_file_location(name, path)
    module = importlib.util.module_from_spec(spec)
    exec(compile(path.read_bytes(), str(path), 'exec'), module.__dict__)
    sys.modules[name] = module
    return module

ac_inlet = load_local_module('ac_inlet')
feet = load_local_module('feet')
dust_cover = load_local_module('dust_cover')
hinges = load_local_module('hinges')
fascia = load_local_module('fascia')
nameplate = load_local_module('nameplate')
assembly_pose = load_local_module('assembly_pose')
model_sections = load_local_module('model_sections')
mechanism_study = load_local_module('mechanism_study')
build_model = load_local_module('build_model')
render_views = load_local_module('render_views')
dimension_sheet = load_local_module('dimension_sheet')
doc, parameters, sections = build_model.deliver()
render_views.render(doc, parameters, sections)
dimension_sheet.create(doc, parameters)

mechanism_study.render_study(doc, json.loads(doc.StudyBasis.ConfigurationJSON))
assembly_pose.set_cover_angle(doc, parameters, parameters['cover_angle_open'])
Gui.activeDocument().activeView().fitAll()
doc.save()
report = json.loads((macro_path.parent.parent / 'cad/mechanism-fit-report.json').read_text())
mechanism_study.save_report(report, macro_path.parent.parent)
