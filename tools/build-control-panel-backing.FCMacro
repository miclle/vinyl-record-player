# Export this backing plate only; never save the control panel or main assembly.
from pathlib import Path
import sys
import FreeCAD as App
import FreeCADGui as Gui

tools = Path(__file__).resolve().parent
if str(tools) not in sys.path:
    sys.path.insert(0, str(tools))
source = tools / 'build_control_panel_backing.py'
namespace = {'__name__': 'backing_macro', '__file__': str(source)}
exec(compile(source.read_bytes(), str(source), 'exec'), namespace)
namespace['export']()
doc = App.openDocument(str(namespace['OUTPUT'] / 'Control-panel-backing.FCStd'))
if not doc.Backing.ViewObject.Visibility:
    raise RuntimeError('Saved backing reopened hidden')
Gui.getDocument(doc.Name).activeView().fitAll()
